--------------------------------------------------------------------------------
-- custom TCAP message definition
-- without parameterization
--------------------------------------------------------------------------------

TCAPMessages DEFINITIONS IMPLICIT TAGS ::=
BEGIN

IMPORTS 
  OPERATION,
  ERROR
  FROM Remote-Operations-Useful-Definitions {joint-iso-itu-t
    remote-operations(4) useful-definitions(7) version1(0)};

--
-- ROS
--

InvokeId ::= CHOICE {
  present  INTEGER,
  absent   NULL
  }

Invoke ::= SEQUENCE {
  invokeId InvokeId,
  linkedId CHOICE {
    present  [0] IMPLICIT INTEGER,
    absent   [1] IMPLICIT NULL
    } OPTIONAL,
  opcode OPERATION.&operationCode,
  argument OPERATION.&ArgumentType OPTIONAL
  }

ReturnResult ::= SEQUENCE {
  invokeId InvokeId,
  result SEQUENCE {
    opcode OPERATION.&operationCode,
    result OPERATION.&ResultType OPTIONAL
    }
  }

ReturnError ::= SEQUENCE {
  invokeId InvokeId,
  errcode ERROR.&errorCode,
  parameter ERROR.&ParameterType OPTIONAL
  }

GeneralProblem ::= INTEGER {
  unrecognizedPDU(0), mistypedPDU(1), badlyStructuredPDU(2)
  }

InvokeProblem ::= INTEGER {
  duplicateInvocation(0), unrecognizedOperation(1), mistypedArgument(2),
  resourceLimitation(3), releaseInProgress(4), unrecognizedLinkedId(5),
  linkedResponseUnexpected(6), unexpectedLinkedOperation(7)
  }

ReturnResultProblem ::= INTEGER {
  unrecognizedInvocation(0), resultResponseUnexpected(1), mistypedResult(2)
}

ReturnErrorProblem ::= INTEGER {
  unrecognizedInvocation(0), errorResponseUnexpected(1), unrecognizedError(2),
  unexpectedError(3), mistypedParameter(4)
  }

RejectProblem ::= INTEGER {
  general-unrecognizedPDU(0), general-mistypedPDU(1),
  general-badlyStructuredPDU(2), invoke-duplicateInvocation(10),
  invoke-unrecognizedOperation(11), invoke-mistypedArgument(12),
  invoke-resourceLimitation(13), invoke-releaseInProgress(14),
  invoke-unrecognizedLinkedId(15), invoke-linkedResponseUnexpected(16),
  invoke-unexpectedLinkedOperation(17),
  returnResult-unrecognizedInvocation(20),
  returnResult-resultResponseUnexpected(21), returnResult-mistypedResult(22),
  returnError-unrecognizedInvocation(30),
  returnError-errorResponseUnexpected(31), returnError-unrecognizedError(32),
  returnError-unexpectedError(33), returnError-mistypedParameter(34)
  }

Reject ::= SEQUENCE {
  invokeId  InvokeId,
  problem CHOICE {
    general       [0]  GeneralProblem,
    invoke        [1]  InvokeProblem,
    returnResult  [2]  ReturnResultProblem,
    returnError   [3]  ReturnErrorProblem
    }
  }

ROS ::= CHOICE {
  invoke        [1]  Invoke,
  returnResult  [2]  ReturnResult,
  returnError   [3]  ReturnError,
  reject        [4]  Reject
  }

--
-- EXTERNAL
--

--EXTERNAL ::= [UNIVERSAL 8] IMPLICIT SEQUENCE {
--  identification [0] EXPLICIT CHOICE {
--    syntax [1] OBJECT IDENTIFIER,
--    presentation-context-id [2] INTEGER,
--    context-negotiation [3] SEQUENCE {
--      presentation-context-id [0] INTEGER,
--      transfer-syntax [1] OBJECT IDENTIFIER
--      },
--    },
--  data-value-descriptor [1] OCTET STRING OPTIONAL,
--  data-value [2] OCTET STRING
--  }

--
-- TCAP
--

DialoguePortion ::= [APPLICATION 11] EXPLICIT EXTERNAL

OrigTransactionID ::= [APPLICATION 8]  OCTET STRING(SIZE (1..4))

DestTransactionID ::= [APPLICATION 9]  OCTET STRING(SIZE (1..4))

P-AbortCause ::= [APPLICATION 10] INTEGER {
  unrecognizedMessageType(0), unrecognizedTransactionID(1),
  badlyFormattedTransactionPortion(2), incorrectTransactionPortion(3),
  resourceLimitation(4)
  } (0..127)

Component ::= CHOICE {
  basicROS ROS,
  returnResultNotLast ReturnResult
  }

ComponentPortion ::= [APPLICATION 12]  SEQUENCE SIZE (1..MAX) OF Component

Unidirectional ::= SEQUENCE {
  dialoguePortion  DialoguePortion OPTIONAL,
  components       ComponentPortion
  }

Begin ::= SEQUENCE {
  otid             OrigTransactionID,
  dialoguePortion  DialoguePortion OPTIONAL,
  components       ComponentPortion OPTIONAL
  }

End ::= SEQUENCE {
  dtid             DestTransactionID,
  dialoguePortion  DialoguePortion OPTIONAL,
  components       ComponentPortion OPTIONAL
  }

Continue ::= SEQUENCE {
  otid             OrigTransactionID,
  dtid             DestTransactionID,
  dialoguePortion  DialoguePortion OPTIONAL,
  components       ComponentPortion OPTIONAL
  }

Abort ::= SEQUENCE {
  dtid    DestTransactionID,
  reason  CHOICE {p-abortCause  P-AbortCause,
                  u-abortCause  DialoguePortion} OPTIONAL
  }

TCMessage ::= CHOICE {
  unidirectional  [APPLICATION 1]  Unidirectional,
  begin           [APPLICATION 2]  Begin,
  end             [APPLICATION 4]  End,
  continue        [APPLICATION 5]  Continue,
  abort           [APPLICATION 7]  Abort
  }

END
